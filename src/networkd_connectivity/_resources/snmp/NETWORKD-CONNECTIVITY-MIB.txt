NETWORKD-CONNECTIVITY-MIB DEFINITIONS ::= BEGIN

IMPORTS
    MODULE-IDENTITY, OBJECT-TYPE, enterprises, Integer32
        FROM SNMPv2-SMI
    DisplayString
        FROM SNMPv2-TC;

networkdConnectivityMIB MODULE-IDENTITY
  LAST-UPDATED "202505010000Z"
  ORGANIZATION "russdill.github.io"
  CONTACT-INFO "russ.dill@gmail.com"
  DESCRIPTION     "MIB module for per-interface connectivity state."
  ::= { enterprises 99999 }

networkdConnectivityTable OBJECT-TYPE
    SYNTAX      SEQUENCE OF NetworkdConnectivityEntry
    MAX-ACCESS  not-accessible
    STATUS      current
    DESCRIPTION "A table of connectivity states for each interface."
    ::= { networkdConnectivityMIB 1 }

networkdConnectivityEntry OBJECT-TYPE
    SYNTAX      NetworkdConnectivityEntry
    MAX-ACCESS  not-accessible
    STATUS      current
    DESCRIPTION "An entry containing ifIndex and its connectivity."
    INDEX       { ifIndex }
    ::= { networkdConnectivityTable 1 }

NetworkdConnectivityEntry ::= SEQUENCE {
    ifIndex           Integer32,
    connectivityState  INTEGER,
    connectivityString DisplayString
}

ifIndex OBJECT-TYPE
    SYNTAX      Integer32 (1..2147483647)
    MAX-ACCESS  read-only
    STATUS      current
    DESCRIPTION "The SNMP ifIndex of the interface."
    ::= { networkdConnectivityEntry 1 }

connectivityState OBJECT-TYPE
    SYNTAX      INTEGER {
                   unknown(0),
                   none(1),
                   portal(2),
                   limited(3),
                   full(4)
                }
    MAX-ACCESS  read-only
    STATUS      current
    DESCRIPTION "Connectivity state (0..4) as per networkd-connectivity."
    ::= { networkdConnectivityEntry 2 }

connectivityString OBJECT-TYPE
    SYNTAX      DisplayString
    MAX-ACCESS  read-only
    STATUS      current
    DESCRIPTION "Connectivity state as a human-readable string."
    ::= { networkdConnectivityEntry 3 }

END
